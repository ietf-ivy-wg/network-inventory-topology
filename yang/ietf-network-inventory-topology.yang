module ietf-network-inventory-topology {
  yang-version 1.1;
  namespace
    "urn:ietf:params:xml:ns:yang:ietf-network-inventory-topology";
  prefix nwit;

  import ietf-network {
    prefix nw;
    reference
      "RFC 8345: A YANG Data Model for Network Topologies,
                 Section 4.1";
  }
  import ietf-network-topology {
    prefix nt;
    reference
      "RFC 8345: A YANG Data Model for Network Topologies,
                 Section 4.2";
  }
  import ietf-network-inventory {
    prefix nwi;
    reference
      "RFC AAAA: A Base YANG Data Model for Network Inventory";
  }

  organization
    "IETF Network Inventory YANG (ivy) Working Group";
  contact
    "WG Web:   https://datatracker.ietf.org/wg/ivy
     WG List:  IVY <mailto:ivy@ietf.org>

     Editor: Bo Wu
             <lana.wubo@huawei.com>
     Editor: Mohamed Boucadair
             <mohamed.boucadair@orange.com>
     Author: Cheng Zhou
             <zhouchengyjy@chinamobile.com>
     Author: Qin Wu
             <bill.wu@huawei.com>";
  description
    "This module defines a YANG module for network
     topology and inventory mapping.

     Copyright (c) 2026 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     All revisions of IETF and IANA published modules can be found
     at the YANG Parameters registry group
     (https://www.iana.org/assignments/yang-parameters).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-10-19 {
    description
      "Initial revision.";
    reference
      "RFC XXXX: A Network Data Model for Inventory Topology
                 Mapping";
  }

  identity link-type {
    description
      "Base identity for classifying the physical media type of a
       link at the inventory topology layer. Additional identities
       may be defined to cover other media types.";
  }

  identity copper {
    base link-type;
    description
      "Copper-based physical link.";
  }

  identity fiber {
    base link-type;
    description
      "Fiber-based physical link.";
  }

  identity coax {
    base link-type;
    description
      "Coaxial cable-based physical link.";
  }

  identity microwave {
    base link-type;
    description
      "Microwave-based wireless link.

       Detailed microwave radio attributes are defined in the
       microwave topology data model.";
    reference
      "RFC 9656: A YANG Data Model for Microwave Topology";
  }

  identity wlan {
    base link-type;
    description
      "IEEE 802.11 wireless link.";
  }

  identity unknown {
    base link-type;
    description
      "The link media type is unknown or could not be determined.

       This identity is used as a fallback when the physical medium
       cannot be classified into any of the other defined types.

       When a discovery system is unable to determine the media
       type, it SHOULD use this identity rather than leaving the
       leaf unset. An unset leaf indicates that the link type has
       not been assessed, whereas unknown explicitly records that
       the medium could not be classified.";
  }

  identity leased-fiber {
    base fiber;
    description
      "Leased fiber link.  The physical medium is fiber, but the link
       is provided by a third-party operator.  Detailed physical
       attributes are typically not visible to the lessee.";
  }

  augment "/nw:networks/nw:network/nw:network-types" {
    description
      "Introduces a new network type for inventory topology
       mapping.";
    container inventory-topology {
      presence
        "Indicates a physical network topology, containing
         physical-layer attributes including inventory mapping, port
         breakout capabilities, and link media types.";
      description
        "Container for the inventory-topology network type.

         When present, it signals that the network contains
         physical-layer augmentations as defined in this module.
         This network type is typically discovered by the network
         controller to identify a physical underlay network; it may
         be configured manually when discovery is not available.

         This network type is intended to serve as the underlay
         for logical network topologies (Layer 2, Layer 3,
         Traffic Engineering (TE), etc.).";
    }
  }

  augment "/nw:networks/nw:network/nw:node" {
    when '../nw:network-types/nwit:inventory-topology';
    description
      "Augments the network topology node with inventory mapping
       attributes. This enables correlation between the physical node
       and its corresponding network element in the inventory.";
    container inventory-mapping-attributes {
      must 'ne-ref' {
        error-message
          "A physical node must include ne-ref to identify the
           corresponding network element.";
      }
      presence
        "If present, an inventory mapping is declared for this node.
         If absent, no inventory mapping is declared.";
      description
        "Container for inventory mapping attributes of a node.

         In typical deployments, the ne-ref leaf SHOULD be populated
         through automatic discovery.  It SHOULD NOT be configured
         manually except where discovery is not possible (e.g.,
         Customer Premises Equipment (CPE) outside the operator's
         management domain).";
      leaf ne-ref {
        type nwi:ne-ref;
        description
          "Reference to the NE in the inventory that corresponds to
           this topology node.

           When the container inventory-mapping-attributes
           is present, this reference identifies the NE that the
           topology node maps to.";
      }
    }
  }

  augment "/nw:networks/nw:network/nt:link" {
    when '../nw:network-types/nwit:inventory-topology';
    description
      "Augments the physical network topology link with
       inventory-related attributes.";
    container inventory-mapping-attributes {
      must 'link-type' {
        error-message
          "A physical link must include link-type to classify the
           link media type.";
      }
      presence
        "If present, an inventory mapping is declared for this link.
         If absent, no inventory mapping is declared.";
      description
        "Container for inventory-related attributes of a link.

         This container provides lightweight media classification.
         The link-type indicates which specialized inventory model
         contains detailed resource information:

         - Wired media (fiber, copper): passive network inventory
         - Wireless media (microwave, wlan): wireless-specific
           inventory

           Detailed inventory references may be added in future
           modules.

           In typical deployments, the link-type leaf SHOULD be
           populated through automatic discovery.  It SHOULD NOT be
           configured manually except where discovery is not possible
           (e.g., leased lines).";
      leaf link-type {
        type identityref {
          base link-type;
        }
        description
          "Classification of the link media type at the topology
           layer.

           The base identity 'link-type' is extensible. Examples
           of derived identities include 'copper', 'fiber',
           'coax', 'microwave', and 'wlan'.

           This leaf serves as a lightweight discriminator.  When
           the value is 'microwave', detailed microwave link
           attributes are defined in the microwave topology data
           model. Wired media (e.g., fiber, copper, or coax) may
           be detailed in a passive network inventory data
           model.";
      }
    }
  }

  augment "/nw:networks/nw:network/nw:node/nt:termination-point" {
    when '../../nw:network-types/nwit:inventory-topology';
    description
      "Augments the termination point (TP) with inventory mapping
       and port breakout.";
    container inventory-mapping-attributes {
      must "nwit:ne-ref =
            ../../nwit:inventory-mapping-attributes/nwit:ne-ref" {
        error-message
          "A physical TP must have a ne-ref that matches the
           ne-ref of its parent node, so that port-ref is
           resolved within a single unambiguous network element
           scope.";
      }
      presence
        "If present, an inventory mapping is declared for this TP.
         If absent, no inventory mapping is declared.";
      description
        "Container for inventory mapping attributes of a TP.

         In typical deployments, the port-ref leaves SHOULD be
         populated through automatic discovery.  They SHOULD NOT
         be configured manually except where discovery is not
         possible (e.g., CPE outside the operator's management
         domain, leased lines).";
      uses nwi:port-ref {
        refine "port-ref" {
          description
            "Reference to the physical port component in the
             network inventory.

             When the container inventory-mapping-attributes
             is present, this reference identifies the port
             component that the TP maps to. The ne-ref leaf must
             also be present, as component identifiers are scoped
             to a network element.";
        }
      }
    }
    container port-breakout {
      presence
        "Indicates the physical port supports channel breakout.";
      config false;
      description
        "Breakout capability of the physical port represented by
         this TP. One TP maps to one physical port; channels are
         listed here. This container is present only when the
         underlying hardware supports partitioning the port into
         multiple independent channels (e.g., 400G to 4x100G).

         This container is read-only (config false) as it reflects
         hardware-determined state.";
      list breakout-channel {
        key "channel-id";
        description
          "Indicates the list of breakout channels available
           on this port. Each entry represents an independent lane
           or sub-port that can be used for channelized
           interfaces.";
        leaf channel-id {
          type uint16;
          description
            "Records a unique identifier for the breakout channel
             within the scope of the parent port.";
        }
      }
    }
  }
}
